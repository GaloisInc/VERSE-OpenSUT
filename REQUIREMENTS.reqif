# Documentation export by StrictDoc

# Specification: OpenSUT Requirements

## R1 (TEXT)
This document contains all OpenSUT requirements, and was created with the help of `StrictDocs <https://strictdoc.readthedocs.io/en/stable/>`_. For text formatting, the reStructuredText markup syntax is supported, see `the RST cheatsheet <https://bashtage.github.io/sphinx-material/rst-cheatsheet/rst-cheatsheet.html>`_.

If you are new to requirement writing, we recommend reading first the *21 Top Engineering Tips for writing an exceptionally clear requirements document* from QRA (available as `PDF here <https://github.com/GaloisInc/VERSE-OpenSUT/blob/main/docs/QRA_Clear_Requirements.pdf>`_),
then refer to *NASA's checklist for writing good requirements* `here <https://www.nasa.gov/reference/appendix-c-how-to-write-a-good-requirement/>`_.

The OpenSUT requirements are split into different sections and subsections. Each requirement has its section number (e.g. *4.1.1.2 Actuation Logic*) and its Unique Identifier (UID). The section number is used only in this document, the UID guaranteed to be globally unique. On top of UID, we also use StrictDocs' `MID <https://strictdoc.readthedocs.io/en/stable/strictdoc_01_user_guide.html#machine-identifiers-mid>`_. For requirement tracing and coverage measurement, we use primarily the UID.

Requirements that use the word *shall* are binding and must be satisfied, while requirements using the word *should* are non-binding, and can be considered optional or nice-to-have. A *rationale* is provided when appropriate for a given requirement.

## R2: SoW Requirements (SECTION)

### R3 (TEXT)
Derived from the Statement of Work for the purpose of tracing the individual tasks and issues back to the SoW.

### R4: OpenSUT Platform (SECTION)

#### R5 (TEXT)
Task **TA2.1.1**

#### TA2-REQ-42: Task TA2.1.1.A (REQUIREMENT)
Develop the Open SUT primarily using existing components and specifications, including:

* Flight Controller
* AutoPilot
* Secure boot
* Mission Key Management
* Mission Protection System components.


Port a subset of OpenSUT components to run in a pKVM guest VM.
- STATUS: Completed

#### TA2-REQ-44: Task TA2.1.1.B (REQUIREMENT)
Specify entire OpenSUT architecture with SysML, and AADL.
- STATUS: Completed

#### TA2-REQ-45: Task TA2.1.1.C (REQUIREMENT)
Develop VERSE Toolchain specifications for components with rich code-level specifications.
- STATUS: Completed

### R9: Apply VERSE to Open SUT (SECTION)

#### R10 (TEXT)
Task **TA2.1.2**

#### TA2-REQ-46: Task TA2.1.2.A (REQUIREMENT)
Build assurance case for the Open SUT.
- STATUS: Completed

#### TA2-REQ-47: Task TA2.1.2.B (REQUIREMENT)
Apply Verse Development Environment (VDE) to provide qualitative and quantitative feedback.
- STATUS: Completed

#### TA2-REQ-48: Task TA2.1.2.C (REQUIREMENT)
Define system deltas for program evolution and evaluation.
- TAGS: Completed

#### TA2-REQ-49: Task TA2.1.2.D (REQUIREMENT)
Support two Phase 1 continuous integration events.
- TAGS: Completed

## R15: OpenSUT Code Requirements (SECTION)

### R16 (TEXT)
In this section we list requirements about the overall OpenSUT code, its structure, coverage and format.

### TA2-REQ-16: No undefined behavior (REQUIREMENT)
OpenSUT shall not contain any C code with undefined behavior, as defined by Cerberus semantics.
- STATUS: Completed
- RATIONALE: An example of undefined behavior include division by zero, out of bounds array access, integer overflow and null pointer dereference.
- NOTES: This is only valid for the verified application code.

### TA2-REQ-17: MISRA-C compliant code (REQUIREMENT)
OpenSUT application code should be MISRA-C compliant.
- RATIONALE: It is acceptable to choose only a subset of MISRA-C, such that it is supported by open-source tools, or regular IDEs (such as `CLion <https://youtrack.jetbrains.com/articles/CPP-A-191430682>`_).

## R19: OpenSUT Scenario Requirements (SECTION)

### R20 (TEXT)
Requirements related to each OpenSUT scenarios.

### R21: Boot OpenSUT to a known initial state (SECTION)

#### R22 (TEXT)
In this scenario, one or more components of OpenSUT boot using SHAVE Trusted Boot. It means that the application code is measured, hashed, and compared against an expected measure. Only if these values match, the application code is started and the measure is stored in the memory. If they don't match, an error is thrown, the boot is aborted and an error message is possibly sent and logged. If the attestation of each securely booted component passes, the system will be in a known initial state, fully provisioned. Measured boot ensures that only the expected code is running on OpenSUT.

The code is measured either with SHA256 or with quantum safe eXtended Merkle Signature Scheme (XMSS).

For the purpose of this scenario, we assume that each host computer contains a root of trust, a trusted boot that can bring up the hypervisor. In other words, we assume the host OS to be trusted (see the Threat model). Because hardware root of trust, trusted boot and attestation are all complex topics, only the application code will be attested in this scenario.

#### TA2-REQ-20: Signature of application code image (REQUIREMENT)
Each application disk image shall contain a digital signature that can be verified by the secure boot.
- STATUS: Completed
- Parent -> TA2-REQ-19

#### TA2-REQ-19: Secure booting only the application code (REQUIREMENT)
Secure boot shall be used to boot only the application code, and only on a subset of OpenSUT components.
- STATUS: Completed
- RATIONALE: This simplification is consistent with out threat model. Demonstrating Secure Boot only on a subset of components is sufficient.
- Parent -> TA2-REQ-18

#### TA2-REQ-18: Explicit assumptions (REQUIREMENT)
In the provided documentation, explicitly list the assumptions and limitations of OpenSUT, such as:

* this is a contrived example
* true secure boot is not possible unless a *chain of trust* going all the way down to *Hardware Root of Trust* is maintained
* in real system a true *Hardware Security Module* (HSM) - such as the one developed on SEASHIP needs to be deployed on each Host computer, and shared with the guests
- STATUS: Completed

## R26: Component Requirements (SECTION)

### R27 (TEXT)
Component specific requirements are located in this section

### R28: Mission Protection System (MPS) Requirements (SECTION)

#### R29 (TEXT)
An engine protection system, that is redundant, measures engine temperature, and fuel pressure, and shuts down the engine if unsafe values are detected.

The system is connected to two temperature sensors and two fuel pressure sensors. The system has a control interface that allows the user to enter the maintenance mode, and adjust setpoints and trip channels. This control interface is available via a serial console (UART), and as such can be accessed only when the platform is not in operation (imagine the UART port being hidden behind a body panel).

#### R30: MPS Architectural Requirements (SECTION)

##### TA2-REQ-40: Four instrumentation channels (REQUIREMENT)
MPS shall have four redundant divisions of instrumentation, each containing identical designs, with two instrumentation channels (Fuel Pressure and Temperature), each channel containing:

A. Sensor
B. Data acquisition and filtering
C. Setpoint comparison for trip generation
D. Trip output signal generation
- STATUS: Completed

##### TA2-REQ-41: Actuation logic (REQUIREMENT)
MPS shall have two trains of actuation logic, each containing identical designs:

A. Two-out-of-four coincidence logic of like trip signals
B. Logic to actuate a first device based on an OR of two instrumentation coincidence signals
C. Logic to actuate a second device based on the remaining instrumentation coincidence signal
- STATUS: Completed

#### R33: MPS Functional Requirements (SECTION)

##### TA2-REQ-27: High pressure trip (REQUIREMENT)
MPS shall Trip on high fuel pressure (sensor to actuation)
- STATUS: Completed

##### TA2-REQ-28: High temperature trip (REQUIREMENT)
MPS shall Trip on high temperature (sensor to actuation)
- STATUS: Completed

##### TA2-REQ-29: Voting logic (REQUIREMENT)
MPS shall Vote on like trips using two-out-of-four coincidence
- STATUS: Completed

##### TA2-REQ-30: Automatic actuation (REQUIREMENT)
MPS shall Automatically actuate devices.
- TAGS: Completed

##### TA2-REQ-31: Manual actuation (REQUIREMENT)
MPS shall Manually actuate each device upon receiving a user command.
- STATUS: Completed
- NOTES: This command was received over UART, after the second change event the command is received over a socket.

##### TA2-REQ-32: Operating modes (REQUIREMENT)
MPS shall Select mutually exclusive maintenance and normal operating modes on a per division basis.
- STATUS: Completed

##### TA2-REQ-33: Setpoint adjustment (REQUIREMENT)
MPS shall Perform setpoint adjustment in maintenance mode.
- STATUS: Completed

##### TA2-REQ-34: Maintenance mode bypass (REQUIREMENT)
MPS shall Configure the system in maintenance mode to bypass an instrument channel (prevent it from generating a corresponding active trip output).
- STATUS: Completed

##### TA2-REQ-35: Maintenance mode forced trip (REQUIREMENT)
MPS shall Configure the system in maintenance mode to force an instrument channel to an active trip output state.
- STATUS: Completed

##### TA2-REQ-36: Variables displayed (REQUIREMENT)
MPS shall Display fuel pressure, and engine temperature.
- STATUS: Completed

##### TA2-REQ-37: Trip state displayed (REQUIREMENT)
MPS shall Display each trip output signal state.
- STATUS: Completed

##### TA2-REQ-38: Bypass indication display (REQUIREMENT)
MPS shall Display indication of each channel in bypass.
- STATUS: Completed

##### TA2-REQ-39: Periodic self-test (REQUIREMENT)
MPS shall run Periodic continual self-test of safety signal path (e.g., overlapping from sensor input to actuation output).
- STATUS: Completed

#### R47: MPS Testing Requirements (SECTION)

##### R48 (TEXT)
Traditionally, this section would be called *Verification Requirements*, but in the context of VERSE *verification* means *providing a formal proof*, thus *testing* is a more appropriate label.

##### TA2-REQ-21: Completeness and consistency (REQUIREMENT)
MPS shall demonstrate the Completeness and consistency of requirements
- STATUS: Completed
- NOTES: Achieved via formalization of the requirements in FRET (see the HARDENS assurance case) and via test cases.

##### TA2-REQ-22: Instrumentation independence (REQUIREMENT)
MPS shall demonstrate Independence among the four divisions of instrumentation (inability for the behavior of one division to interfere or adversely affect the performance of another)
- STATUS: Completed

##### TA2-REQ-23: Instrumentation independence within a division (REQUIREMENT)
MPS shall demonstrate Independence among the two instrumentation channels within a division (inability for the behavior of one channel to interfere or adversely affect the performance of another)
- STATUS: Completed

##### TA2-REQ-24: Actuation logic independence (REQUIREMENT)
MPS shall demonstrate Independence among the two trains of actuation logic (inability for the behavior of one train to interfere or adversely affect the performance another)
- STATUS: Completed

##### TA2-REQ-25: Actuation on coincidence vote or manual action (REQUIREMENT)
MPS shall demonstrate Completion of actuation whenever coincidence logic is satisfied or manual actuation is initiated.
- STATUS: Completed

##### TA2-REQ-26: Self test and trip independence (REQUIREMENT)
MPS shall demonstrate Independence between periodic self-test functions and trip functions (inability for the behavior of the self-testing to interfere or adversely affect the trip functions)
- STATUS: Completed

### R55: Secure Boot Requirements (SECTION)

#### R56 (TEXT)
A system boot where aspects of the hardware and firmware are measured and compared against known good values to verify their integrity and thus their trustworthiness.

#### R57: Secure Boot Functional Requirements (SECTION)

##### TA2-REQ-54: Known initial state (REQUIREMENT)
The Secure Boot shall bring a given component to a known initial state.
- STATUS: Completed
- Parent -> TA2-REQ-19

##### TA2-REQ-65: Code attestation (REQUIREMENT)
Secure boot shall provide attestation for the application code.
- STATUS: Completed

##### TA2-REQ-55: Boot debug information (REQUIREMENT)
The Secure Boot shall print information to the console/serial port for debugging purposes.
- STATUS: Completed

##### TA2-REQ-56: Secure boot termination (REQUIREMENT)
The Secure Boot shall always terminate.
- STATUS: Deferred
- NOTES: CN cannot currently prove termination properties

##### TA2-REQ-57: Launch application or terminate (REQUIREMENT)
The Secure boot shall either launch the application, or if an error occurs, log the error and terminate.
- STATUS: Completed

##### TA2-REQ-58: Clear memory (REQUIREMENT)
The Secure boot shall erase all RAM containing the secure boot data before a handoff to the application code.
- STATUS: Deferred
- RATIONALE: This prevents accidental leakage of private information to the potentially compromised application, such as private keys or attestation information.
- NOTES: Memory erasing is difficult to achieve for a linux process. This requirement will be relevant for embedded scenarios.

#### R64: Secure Boot Security Requirements (SECTION)

##### TA2-REQ-60: Measurement algorithm (REQUIREMENT)
The Secure Boot shall use high assurance implementation of cryptographic algorithms.
- STATUS: Completed
- RATIONALE: For example an implementation that has been formally verified against a "golden" specification, or an implementation automatically generated from such "golden specification".

##### TA2-REQ-59: Binary code measurement (REQUIREMENT)
The Secure Boot shall measure the application binary and compare it against a stored good known value.
- STATUS: Completed
- Parent -> TA2-REQ-20

##### TA2-REQ-61: Secure store of the hash measurement (REQUIREMENT)
The Secure Boot should store the measured values in a Trusted Platform Module or other secure memory storage.
- STATUS: Deferred
- RATIONALE: Normally this requirement would be binding ("shall"), but given the scope of our threat model, this requirement is optional ("should").
- NOTES: No TPM available.

##### TA2-REQ-62: Abort on mismatched measurements (REQUIREMENT)
The Secure Boot shall abort the boot process and throw an error, if the expected and measured values do not match.
- STATUS: Completed

##### TA2-REQ-63: Secure Boot stored in read-only memory (REQUIREMENT)
The Secure Boot executable shall be stored in a read only memory, or with read-only permissions.
- STATUS: Deferred
- RATIONALE: This avoids possible modifications to the secure boot executable.
- NOTES: Not implemented, as for simpler execution we run the secure boot and the application code in the same userspace.

##### TA2-REQ-64: Do not compare measurements if expected value is not provided (REQUIREMENT)
If no expected value of the application binary is provided, the secure boot shall only perform a measurement, save it, and launch the application.
- STATUS: Completed
- RATIONALE: If an application is not signed, the secure boot measurement comparison is disabled.

### R71: Mission Key Management Requirements (SECTION)

#### R72 (TEXT)
Mission Key Management (MKM) processes key requests and distributes keys to other components. Any component can connect to the MKM, request a key, and attest to the code that it's running; the MKM will then send the key if allowed by the MKM's built-in policy.

We require the MKM to implement the following protocol:

1. The client connects to the MKM over TCP.
2. The client component sends a key ID (1 byte), indicating which key it is
   requesting.
3. The MKM sends a random nonce (16 bytes).
4. The client obtains an attestation matching the challenge (by communicating
   with its trusted boot daemon) and sends the attestation (64 bytes).
5. If the attestation is valid and MKM policy allows the component to receive
   the requested key, the MKM sends the key (32 bytes).

If an error occurs, such as an invalid attestation or a policy violation, the
MKM simply closes the connection without sending the key.

Since all messages have a fixed size and occur in a fixed order, the protocol
does not use any headers or delimiters for messages.

The MKM server listens on localhost (127.0.0.1) port 6000 by default.  To
change this, set the `MKM_BIND_ADDR` and/or `MKM_PORT` environment variables.
For example, `MKM_BIND_ADDR=0.0.0.0 MKM_PORT=6001 ./mkm config.bin` will cause
it to listen on port 6001 on all network interfaces.

## R73: VERSE Toolchain Requirements (SECTION)

### R74 (TEXT)
VERSE Toolchain specific requirements, driven by the TA2 needs.

### R75: VERSE Toolchain Usability Requirements (SECTION)

#### R76 (TEXT)
Requirements related to the user experience with VERSE Toolchain in general.

#### TA2-REQ-1: No crashing (REQUIREMENT)
VERSE Toolchain shall not crash on arbitrary input. Instead, an error message shall be produced.
- STATUS: Deferred
- RATIONALE: Even if a specification is incorrect, or the input file is not a valid C code, VERSE Toolchain should gracefully exit.
- NOTES: Guaranteeing this requirement for all possible inputs was beyond the scope of the TA1 team's effort.

#### TA2-REQ-2: Special delimiters (REQUIREMENT)
VERSE Toolchain should support multiple special delimiters, such as `//@` or `/*@` or `/**@`. Which special delimiter should be used can be either configurable, or VERSE Toolchain should support all of them at the same time (see TA2-REQ-15).
- STATUS: Completed
- RATIONALE: In some codebases, VERSE Toolchain specs need to co-exist with existing specifications (such as Frama-C ACSL), such that adding VERSE Toolchain specs does not break the existing proofs.
- Parent -> TA2-REQ-7

#### TA2-REQ-7: Multiple specification languages (REQUIREMENT)
VERSE Toolchain shall run on codebases with multiple specification languages, such as Frama-C, SAW, and Cryptol.
- STATUS: Completed
- RATIONALE: High assurance code might contain multiple different spec languages. For VERSE program, we expect that only Frama-C ACSL specifications will exist directly in the C source code. Other specs, such as SAW and Cryptol, do not change the C code directly.

#### TA2-REQ-8: Continuity of existing proofs (REQUIREMENT)
Adding VERSE Toolchain specs to a codebase shall not break existing proofs about such codebase.
- STATUS: Completed
- RATIONALE: For example, adding VERSE Toolchain specs into an existing high assurance codebase shall not break the existing Frama-C proofs
- NOTES: We run both Frama-C and CN proofs in the CI
- Parent -> TA2-REQ-7

#### TA2-REQ-15: Project specific VERSE Toolchain configuration (REQUIREMENT)
VERSE Toolchain shall support project specific configuration, in the form of a configuration file that will adjust how VERSE Toolchain behaves.
- STATUS: Deferred
- RATIONALE: This is a top level requirement, further specified in the child requirements.
- NOTES: Out of scope for P1

#### TA2-REQ-52: Code similarity (REQUIREMENT)
The code checked by VERSE Toolchain and the code compiled and deployed on the OpenSUT shall be identical.
- STATUS: Deferred
- RATIONALE: If the code that can be checked by VERSE Toolchain is substantially different from the code that is compiled and deployed, errors in the production code might not be captured, leading to presence of bugs and vulnerabilities.
- NOTES: While the code is fairly similar, there are still some workarounds needed for the verification to pass.

### R83: VERSE Toolchain Functional Requirements (SECTION)

#### R84 (TEXT)
This section lists requirements on the functionality of VERSE Toolchain, and the features it provides.

#### TA2-REQ-3: Versioned releases (REQUIREMENT)
VERSE Toolchain shall provide versioned releases, such that running VERSE Toolchain with `-V` flag shall print out the version of the tool.
- STATUS: Completed
- NOTES: CN prints the commit hash as a version.

#### TA2-REQ-5: Variadic functions (REQUIREMENT)
VERSE Toolchain shall support reasoning about variadic functions, such as `printf()`.
- STATUS: Deferred

#### TA2-REQ-4: Packaged releases (REQUIREMENT)
VERSE Toolchain shall provide packaged releases using industry standard mechanisms, such as docker, or debian packages.
- STATUS: Completed
- NOTES: CN provides both Ubuntu and RedHat based docker images.

#### TA2-REQ-6: C Unions (REQUIREMENT)
VERSE Toolchain shall support reasoning about C union types.
- STATUS: Deferred
- RATIONALE: For example the MPS code relies heavily on unions, and such code needs to be supported.
- NOTES: Planned for Phase 2

#### TA2-REQ-9: Nested types (REQUIREMENT)
VERSE Toolchain shall support reasoning about structs composed of other structs.
- STATUS: Deferred
- RATIONALE: For example VERSE Toolchain shall be able to reason about the following struct and prove that there is no undefined behavior and that any user defined specification holds for such a struct:

  .. code-block:: c

      struct S {
          T1 S1;
          T2 *S2;
          T3 S3[];
      }

#### TA2-REQ-53: User defined type invariants (REQUIREMENT)
VERSE Toolchain should support checking user defined type and data structure invariants. VERSE Toolchain should allow users to annotate types and data structures with invariants, such that the invariant is preserved at every instance of that type.
- STATUS: Completed
- RATIONALE: For example, the user wishes to prove that a pointer of particular type is never NULL. While NULL pointers are allowed under Cerberus C semantics, *dereferencing* a NULL pointer is an undefined behavior. Thus, a user defined invariant that a pointer shall never be NULL should be checkable by VERSE Toolchain.

  Or given an array `T3 S3[];` the user wishes to prove that invariants about type T3 are valid for each element of array S3, and this is true for min and max size of S3, with min=0 and max some sensible default value (uint32_MAX?).

#### TA2-REQ-10: Specs in header of source file allowed (REQUIREMENT)
VERSE Toolchain shall allow the user to write VERSE Toolchain specifications in either header (function declaration) or source file (function definition). If VERSE Toolchain specs are provided at both function declaration and function definition, VERSE Toolchain shall raise an error.
- STATUS: Completed
- RATIONALE: In some cases, writing specs in the header files is more ergonomic. In other cases, there might be no header files. The user shall have a choice that is the most suitable for a particular codebase. If accidentally the user writes multiple VERSE Toolchain specs for the same function (in the header and in the source file), VERSE Toolchain needs to throw an error an notify the user, as resolving which specs are valid is a complex problem.

#### TA2-REQ-12: Explicit assertion checking (REQUIREMENT)
VERSE Toolchain shall have a configurable option to either ignore inline `assert()` statements, or to statically check them.
- STATUS: Deferred
- RATIONALE: In some codebases, assertions are used only for selective runtime testing, so static checking might produce findings that are not interesting for the developers. The assertions are removed in the production code. Hence having the configurable option for VERSE Toolchain is important.
- NOTES: Planned for Phase 2
- Parent -> TA2-REQ-15

#### TA2-REQ-13: Well defined default behavior (REQUIREMENT)
If a function is not annotated with any VERSE Toolchain specifications, VERSE Toolchain shall explicitly state what are the default (implicit) `require`, `ensure` and `modify` clauses.
- STATUS: Deferred
- RATIONALE: It needs to be stated whether by default each function requires and ensures nothing, or if there are some implicit assumptions, important for compositional reasoning. Same for modification - a sensible default behavior could be that a function without specs is assumed to modify everything. However, in that case compositional reasoning is not really possible, so having a configurable option here might be preferred.

  The implicit `requires` might encompass e.g. a valid stack frame for the function.
- NOTES: Planned in Phase 2, as a part of the documentation improvement.
- Parent -> TA2-REQ-15

#### TA2-REQ-14: Annotation of pure functions (REQUIREMENT)
VERSE Toolchain shall have a configurable option to either assume that all functions are `pure` by default, or to require an explicit `pure` annotation.
- STATUS: Deferred
- RATIONALE: Pure functions are side-effects free, and don't have any persistent static variables (see https://en.wikipedia.org/wiki/Pure_function). In some cases, explicitly stating which functions should be `pure` is easier, while in other codebases, it is reasonable to assume that the functions are `pure` by default. This should be configurable.
- Parent -> TA2-REQ-15

#### TA2-REQ-51: Check for undefined behavior (REQUIREMENT)
VERSE Toolchain shall check C code for undefined behavior as defined in Cerberus semantics, and raise an error when undefined behavior is found.
- STATUS: Completed
- RATIONALE: This is a base level functionality of VERSE Toolchain, as code with undefined behavior often leads to errors and unintended results.
- Parent -> TA2-REQ-16

### R96: VERSE Toolchain Documentation Requirements (SECTION)

#### R97 (TEXT)
Documentation of VERSE Toolchain, including manuals, tutorials, quick-start guides, code and document generation, and hints and error messages.

#### TA2-REQ-11: Generating code documentation with specs (REQUIREMENT)
TA1 tools shall generate source code documentation that includes VERSE Toolchain specification with VERSE Toolchain syntax highlighted.
- STATUS: Deferred
- RATIONALE: Doxygen-like documentation with VERSE Toolchain specs included is ideal. It is important that the specs are not treated like comments, but are lifted and highlighted in the generated documents.

#### TA2-REQ-50: Code coverage measurement (REQUIREMENT)
VERSE Toolchain should provide means of measuring code coverage, and specifically reporting:

1) percentage or LOC of code/functions that have *any* specs
2) *any* code excluded from VERSE Toolchain checking (maybe hiding behind `#ifdef` or some other directive, excluding the code from being examined)
3) coverage based on types/classes of specifications (see the different classes we mentioned in the proposal)
- STATUS: Deferred
- RATIONALE: See https://github.com/GaloisInc/VERSE-Toolchain/issues/93 for more details.
